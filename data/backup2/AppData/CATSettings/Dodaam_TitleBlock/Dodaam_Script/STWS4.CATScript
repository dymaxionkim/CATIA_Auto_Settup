Dim storePath as String

' Sub to read the Store Path
function readSPath()
os=UCase(Left(CATIA.SystemConfiguration.OperatingSystem, 3))
sep="/"
If (os = "WIN") Or (os = "INT") Then
  sep="\"
end if
if (len(storePath)=0) then
  ret = InputBox("Enter Path for CATPart or CATProduct (e.g. c:"+sep+"catfiles"+sep+")","Save as")
  storePath=ret
end if
Set fso = CreateObject("Scripting.FileSystemObject")
if (len(storePath)=0) OR (fso.FolderExists(storePath) = false) then
  Set fso = Nothing
  readSPath=empty
  exit function
end if
if mid(storePath,Len(storePath),1)<>sep then
  storePath=storePath+sep
end if
readSPath=storePath
Set fso = Nothing
end function


' Sub to store a document'
sub saveDocument(document,name)
  document.SaveAs storePath & name
end sub

function getUCaseName(name)
dim ret
ucaseName = Left(name,InStrRev(name,".")-1)
extension = Right(name,len(name)-InStr(name,".")+1)
getUCaseName=UCASE(ucaseName)+extension
end function
' *** tools function '
function toolCall0(PartDocument,HybridBody1)
PartDocument.Part.InWorkObject =HybridBody1
PartDocument.Part.Update
set hypFact=PartDocument.Part.HybridShapeFactory
Set HybridShapePointCoord0 = hypFact.AddNewPointCoord  ( 0,0,0) 
HybridBody1.AppendHybridShape HybridShapePointCoord0
PartDocument.Part.InWorkObject =HybridShapePointCoord0
PartDocument.Part.Update
Set HybridShapePointCoord1 = hypFact.AddNewPointCoord  ( 0,0,-1) 
HybridBody1.AppendHybridShape HybridShapePointCoord1
PartDocument.Part.InWorkObject =HybridShapePointCoord1
PartDocument.Part.Update
Set HybridShapePointCoord2 = hypFact.AddNewPointCoord  ( 0,1,0) 
HybridBody1.AppendHybridShape HybridShapePointCoord2
PartDocument.Part.InWorkObject =HybridShapePointCoord2
PartDocument.Part.Update
set Reference0 = PartDocument.Part.CreateReferenceFromGeometry  ( HybridShapePointCoord0 ) 
set Reference1 = PartDocument.Part.CreateReferenceFromGeometry  ( HybridShapePointCoord1 ) 
set Reference2 = PartDocument.Part.CreateReferenceFromGeometry  ( HybridShapePointCoord2 ) 
Set absPlane = hypFact.AddNewPlane3Points  ( Reference0, Reference1, Reference2 ) 
HybridBody1.AppendHybridShape absPlane
PartDocument.Part.InWorkObject =absPlane
PartDocument.Part.Update
Set absRef = PartDocument.Part.CreateReferenceFromGeometry(absPlane)
PartDocument.Part.Update
set toolCall0=absref
end function
function toolCall1(partdocument,body,absref)
PartDocument.Part.InWorkObject = Body
set sketch= Body.Sketches.Add  ( absRef )
PartDocument.Part.InWorkObject =sketch
PartDocument.Part.Update
set factory2d=sketch.OpenEdition
Set Axis2D7 = Sketch.AbsoluteAxis
Set Line2D8 = Axis2D7.HorizontalReference
Line2D8.ReportName = 1
Set Line2D9 = Axis2D7.VerticalReference
Line2D9.ReportName = 2
set startPoint=Factory2D.CreatePoint(1.7764227642276,-1.4013715179912)
set endPoint=Factory2D.CreatePoint(-1.7764227642276,-1.4013715179912)
set cir=Factory2D.CreateCircle(1.1102230246252e-16,0.175,2.375,5.5573835075539,3.8673944532155)
cir.StartPoint = startPoint
cir.EndPoint = endPoint
set startPoint=Factory2D.CreatePoint(-1.6,-1.8659862811886)
set endPoint=Factory2D.CreatePoint(-1.7764227642276,-1.4013715179912)
set cir=Factory2D.CreateCircle(-2.3,-1.8659862811886,0.7,0,0.72580179962569)
cir.StartPoint = startPoint
cir.EndPoint = endPoint
set startPoint=Factory2D.CreatePoint(-1.6,-1.8659862811886)
set endPoint=Factory2D.CreatePoint(-1.6,-2.55)
set line=factory2d.CreateLine(-1.6,-1.8659862811886,-1.6,-2.55)
line.startPoint=startPoint
line.endPoint=endPoint
set startPoint=Factory2D.CreatePoint(-1.6,-2.55)
set endPoint=Factory2D.CreatePoint(-0.9,-3.25)
set cir=Factory2D.CreateCircle(-0.9,-2.55,0.7,3.1415926535898,4.7123889803847)
cir.StartPoint = startPoint
cir.EndPoint = endPoint
set startPoint=Factory2D.CreatePoint(-0.9,-3.25)
set endPoint=Factory2D.CreatePoint(-0.025,-3.25)
set line=factory2d.CreateLine(-0.9,-3.25,-0.025,-3.25)
line.startPoint=startPoint
line.endPoint=endPoint
set startPoint=Factory2D.CreatePoint(-0.025,-3.25)
set endPoint=Factory2D.CreatePoint(-0.025,-2.9)
set line=factory2d.CreateLine(-0.025,-3.25,-0.025,-2.9)
line.startPoint=startPoint
line.endPoint=endPoint
set startPoint=Factory2D.CreatePoint(-0.025,-2.9)
set endPoint=Factory2D.CreatePoint(-0.6,-2.9)
set line=factory2d.CreateLine(-0.025,-2.9,-0.6,-2.9)
line.startPoint=startPoint
line.endPoint=endPoint
set startPoint=Factory2D.CreatePoint(-0.6,-2.2)
set endPoint=Factory2D.CreatePoint(-0.6,-2.9)
set cir=Factory2D.CreateCircle(-0.6,-2.55,0.35,1.5707963267949,4.7123889803847)
cir.StartPoint = startPoint
cir.EndPoint = endPoint
set startPoint=Factory2D.CreatePoint(-0.6,-2.2)
set endPoint=Factory2D.CreatePoint(-0.025,-2.2)
set line=factory2d.CreateLine(-0.6,-2.2,-0.025,-2.2)
line.startPoint=startPoint
line.endPoint=endPoint
set startPoint=Factory2D.CreatePoint(-0.025,-2.2)
set endPoint=Factory2D.CreatePoint(-0.025,-1.8498310733686)
set line=factory2d.CreateLine(-0.025,-2.2,-0.025,-1.8498310733686)
line.startPoint=startPoint
line.endPoint=endPoint
set startPoint=Factory2D.CreatePoint(0.025,-1.8498310733686)
set endPoint=Factory2D.CreatePoint(-0.025,-1.8498310733686)
set cir=Factory2D.CreateCircle(-1.7347234759768e-18,-6.7952371160529e-17,1.85,4.7259029052272,4.6988750555422)
cir.StartPoint = startPoint
cir.EndPoint = endPoint
set startPoint=Factory2D.CreatePoint(0.025,-1.8498310733686)
set endPoint=Factory2D.CreatePoint(0.025,-2.2)
set line=factory2d.CreateLine(0.025,-1.8498310733686,0.025,-2.2)
line.startPoint=startPoint
line.endPoint=endPoint
set startPoint=Factory2D.CreatePoint(0.025,-2.2)
set endPoint=Factory2D.CreatePoint(0.6,-2.2)
set line=factory2d.CreateLine(0.025,-2.2,0.6,-2.2)
line.startPoint=startPoint
line.endPoint=endPoint
set startPoint=Factory2D.CreatePoint(0.6,-2.9)
set endPoint=Factory2D.CreatePoint(0.6,-2.2)
set cir=Factory2D.CreateCircle(0.6,-2.55,0.35,4.7123889803847,1.5707963267949)
cir.StartPoint = startPoint
cir.EndPoint = endPoint
set startPoint=Factory2D.CreatePoint(0.6,-2.9)
set endPoint=Factory2D.CreatePoint(0.025,-2.9)
set line=factory2d.CreateLine(0.6,-2.9,0.025,-2.9)
line.startPoint=startPoint
line.endPoint=endPoint
set startPoint=Factory2D.CreatePoint(0.025,-2.9)
set endPoint=Factory2D.CreatePoint(0.025,-3.25)
set line=factory2d.CreateLine(0.025,-2.9,0.025,-3.25)
line.startPoint=startPoint
line.endPoint=endPoint
set startPoint=Factory2D.CreatePoint(0.025,-3.25)
set endPoint=Factory2D.CreatePoint(0.9,-3.25)
set line=factory2d.CreateLine(0.025,-3.25,0.9,-3.25)
line.startPoint=startPoint
line.endPoint=endPoint
set startPoint=Factory2D.CreatePoint(0.9,-3.25)
set endPoint=Factory2D.CreatePoint(1.6,-2.55)
set cir=Factory2D.CreateCircle(0.9,-2.55,0.7,4.7123889803847,0)
cir.StartPoint = startPoint
cir.EndPoint = endPoint
set startPoint=Factory2D.CreatePoint(1.6,-2.55)
set endPoint=Factory2D.CreatePoint(1.6,-1.8659862811886)
set line=factory2d.CreateLine(1.6,-2.55,1.6,-1.8659862811886)
line.startPoint=startPoint
line.endPoint=endPoint
set startPoint=Factory2D.CreatePoint(1.7764227642276,-1.4013715179912)
set endPoint=Factory2D.CreatePoint(1.6,-1.8659862811886)
set cir=Factory2D.CreateCircle(2.3,-1.8659862811886,0.7,2.4157908539641,3.1415926535898)
cir.StartPoint = startPoint
cir.EndPoint = endPoint
PartDocument.Part.Update
Sketch.CloseEdition
set sketch3=sketch
PartDocument.Part.Update
set toolCall1=sketch3
end function
' *** creation code'
Sub CreatePart1

On error Resume next
set SaveCaseDoc=CATIA.Documents.Item("STWS4.CATPart")
If Err.Number<>0 Then
ucaseName=getUCaseName("STWS4.CATPart")
set SaveCaseDoc=CATIA.Documents.Item(ucaseName)
End If
set PartDocument=SaveCaseDoc
if isobject(PartDocument) then
  PartDocument.Activate()
  exit sub
end if

Set fso = CreateObject("Scripting.FileSystemObject")
if fso.FileExists(storePath & "STWS4.CATPart") then
  CATIA.Documents.Open(storePath & "STWS4.CATPart")
  Set fso = Nothing
  exit sub
elseif fso.FileExists(storePath & getUCaseName("STWS4.CATPart")) then
  CATIA.Documents.Open(storePath & getUCaseName("STWS4.CATPart"))
  Set fso = Nothing
  exit sub
end if
Set fso = Nothing
On error Goto 0
Set PartDocument= CATIA.Documents.Add("Part")
Set strParam1=PartDocument.GetItem(1).UserRefProperties.CreateString("NN","STWN, STWS")
Set strParam1=PartDocument.GetItem(1).UserRefProperties.CreateString("NT","Retaining Rings - C - External")
Set strParam1=PartDocument.GetItem(1).UserRefProperties.CreateString("NB","STWS4")
Set strParam1=PartDocument.GetItem(1).UserRefProperties.CreateString("NBSYN","$PN.")
Set strParam1=PartDocument.GetItem(1).UserRefProperties.CreateString("LINA","STWS4")
Set strParam1=PartDocument.GetItem(1).UserRefProperties.CreateString("PN","STWS4")
Set strParam1=PartDocument.GetItem(1).UserRefProperties.CreateString("TYPE","STWS")
Set strParam1=PartDocument.GetItem(1).UserRefProperties.CreateString("MAT","304 Stainless Steel-CSP")
Set strParam1=PartDocument.GetItem(1).UserRefProperties.CreateString("HARD","36~44HRC")
Set strParam1=PartDocument.GetItem(1).UserRefProperties.CreateString("NO","4")
Set strParam1=PartDocument.GetItem(1).UserRefProperties.CreateString("MATALG","'1','Spring Steel','2','304 Stainless Steel-CSP'")
Set strParam1=PartDocument.GetItem(1).UserRefProperties.CreateString("DD3","3.6")
Set strParam1=PartDocument.GetItem(1).UserRefProperties.CreateString("DD3TOL","+0.01/-0.01")
Set strParam1=PartDocument.GetItem(1).UserRefProperties.CreateString("TT","0.25")
Set strParam1=PartDocument.GetItem(1).UserRefProperties.CreateString("TTTOL","+0.03/-0.03")
Set strParam1=PartDocument.GetItem(1).UserRefProperties.CreateString("BB","0.7")
Set strParam1=PartDocument.GetItem(1).UserRefProperties.CreateString("AA","1.4")
Set strParam1=PartDocument.GetItem(1).UserRefProperties.CreateString("DD0","0.7")
Set strParam1=PartDocument.GetItem(1).UserRefProperties.CreateString("DD4","9.0")
Set strParam1=PartDocument.GetItem(1).UserRefProperties.CreateString("DD1","4")
Set strParam1=PartDocument.GetItem(1).UserRefProperties.CreateString("DD2","3.70")
Set strParam1=PartDocument.GetItem(1).UserRefProperties.CreateString("DD2TOL","+0.06/-0.06")
Set strParam1=PartDocument.GetItem(1).UserRefProperties.CreateString("MM","0.30")
Set strParam1=PartDocument.GetItem(1).UserRefProperties.CreateString("MMTOL","+0.10/0")
Set strParam1=PartDocument.GetItem(1).UserRefProperties.CreateString("NN","1.0")
Set strParam1=PartDocument.GetItem(1).UserRefProperties.CreateString("H1","0.700")
Set strParam1=PartDocument.GetItem(1).UserRefProperties.CreateString("A3","0.05")
Set strParam1=PartDocument.GetItem(1).UserRefProperties.CreateString("A2","1.20")
Set strParam1=PartDocument.GetItem(1).UserRefProperties.CreateString("A1","3.20")
Set strParam1=PartDocument.GetItem(1).UserRefProperties.CreateString("R2","0.70")
Set strParam1=PartDocument.GetItem(1).UserRefProperties.CreateString("R1","0.70")
Set strParam1=PartDocument.GetItem(1).UserRefProperties.CreateString("VENDOR","MISUMI")
Set strParam1=PartDocument.GetItem(1).UserRefProperties.CreateString("SUPPLIER","MISUMI")
Set strParam1=PartDocument.GetItem(1).UserRefProperties.CreateString("ARTICLENO","NB")
Set strParam1=PartDocument.GetItem(1).UserRefProperties.CreateString("BOMINFO","LINA")
Set strParam1=PartDocument.GetItem(1).UserRefProperties.CreateString("CREATOR","CADENAS GmbH")
PartDocument.GetItem(1).PartNumber="STWS4"
PartDocument.GetItem(1).Definition="Cadenas PARTsolutions"
PartDocument.GetItem(1).DescriptionRef="NT"
Dim  skCoord ( 8 )
Dim Body As AnyObject
Set Body = PartDocument.Part.Bodies.Item (1)
Dim HybridBody1 As HybridBody
Set HybridBody1 = PartDocument.Part.HybridBodies.Add
PartDocument.Selection.Clear
PartDocument.Selection.Add PartDocument.Part.OriginElements.PlaneXY
PartDocument.Selection.Add PartDocument.Part.OriginElements.PlaneYZ
PartDocument.Selection.Add PartDocument.Part.OriginElements.PlaneZx
PartDocument.Selection.VisProperties.SetShow(1)
PartDocument.Selection.Clear
PartDocument.Selection.Clear
PartDocument.Selection.Add HybridBody1
PartDocument.Selection.VisProperties.SetShow(1)
PartDocument.Selection.Clear
set absref=toolCall0(PartDocument,HybridBody1)
set sketch3=toolCall1(partdocument,body,absref)
PartDocument.Part.InWorkObject = Body
PartDocument.Part.Update
set pad=PartDocument.Part.ShapeFactory.AddNewPad(sketch3,0.125)
Pad.IsSymmetric = True
PartDocument.Part.Update
saveDocument PartDocument,"STWS4.CATPart"
End Sub
sub CreatePSolMain
On error Resume next
set PartDocument=CATIA.Documents.Item("STWS4.CATPart")
if isobject(PartDocument) then
  PartDocument.Activate()
  exit sub
end if
if isempty(readSPath) then
  exit sub
end if
Set fso = CreateObject("Scripting.FileSystemObject")
if fso.FileExists(storePath & "STWS4.CATPart") then
  CATIA.Documents.Open(storePath & "STWS4.CATPart")
  Set fso = Nothing
  exit sub
end if
Set fso = Nothing
On error Goto 0
createPart1

end sub

CreatePsolMain
